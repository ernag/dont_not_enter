RFC1213-MIB DEFINITIONS ::= BEGIN

        DisplayString ::= OCTET STRING
        PhysAddress ::= OCTET STRING

        mib-2           OBJECT IDENTIFIER ::= { mgmt 1 }

        system          OBJECT IDENTIFIER ::= { mib-2 1 }

        interfaces      OBJECT IDENTIFIER ::= { mib-2 2 }

        ip              OBJECT IDENTIFIER ::= { mib-2 4 }

        icmp            OBJECT IDENTIFIER ::= { mib-2 5 }

        tcp             OBJECT IDENTIFIER ::= { mib-2 6 }

        udp             OBJECT IDENTIFIER ::= { mib-2 7 }

        transmission    OBJECT IDENTIFIER ::= { mib-2 10 }

        snmp            OBJECT IDENTIFIER ::= { mib-2 11 }

        sysDescr OBJECT-TYPE
                SYNTAX DisplayString
                ACCESS read-only
                STATUS mandatory
                DESCRIPTION
                        ""
                ::= { system 1 }

        sysObjectID OBJECT-TYPE
                SYNTAX OBJECT IDENTIFIER
                ACCESS read-only
                STATUS mandatory
                DESCRIPTION
                        ""
                ::= { system 2 }

        sysUpTime OBJECT-TYPE
                SYNTAX TimeTicks
                ACCESS read-only
                STATUS mandatory
                DESCRIPTION
                        ""
                ::= { system 3 }

        sysContact OBJECT-TYPE
                SYNTAX DisplayString
                ACCESS read-write
                STATUS mandatory
                DESCRIPTION
                        ""
                ::= { system 4 }

        sysName OBJECT-TYPE
                SYNTAX DisplayString
                ACCESS read-write
                STATUS mandatory
                DESCRIPTION
                        ""
                ::= { system 5 }

        sysLocation OBJECT-TYPE
                SYNTAX DisplayString
                ACCESS read-write
                STATUS mandatory
                DESCRIPTION
                        ""
                ::= { system 6 }

        sysServices OBJECT-TYPE
                SYNTAX INTEGER
                ACCESS read-only
                STATUS mandatory
                DESCRIPTION
                        ""
                ::= { system 7 }

        ifNumber OBJECT-TYPE
                SYNTAX INTEGER
                ACCESS read-only
                STATUS mandatory
                DESCRIPTION
                        ""
                ::= { interfaces 1 }

        ifTable OBJECT-TYPE
                SYNTAX SEQUENCE OF IfEntry
                ACCESS not-accessible
                STATUS mandatory
                DESCRIPTION
                        ""
                ::= { interfaces 2 }

        ifEntry OBJECT-TYPE
                SYNTAX IfEntry
                ACCESS not-accessible
                STATUS mandatory
                DESCRIPTION
                        ""
                INDEX { ifIndex }
                ::= { ifTable 1 }

        IfEntry ::= SEQUENCE { 
            ifIndex INTEGER,
            ifDescr DisplayString,
            ifType INTEGER,
            ifMtu INTEGER,
            ifSpeed Gauge,
            ifPhysAddress PhysAddress,
            ifAdminStatus INTEGER,
            ifOperStatus INTEGER,
            ifLastChange TimeTicks,
            ifInOctets Counter,
            ifInUcastPkts Counter,
            ifInNUcastPkts Counter,
            ifInDiscards Counter,
            ifInErrors Counter,
            ifInUnknownProtos Counter,
            ifOutOctets Counter,
            ifOutUcastPkts Counter,
            ifOutNUcastPkts Counter,
            ifOutDiscards Counter,
            ifOutErrors Counter,
            ifOutQLen Gauge,
            ifSpecific OBJECT IDENTIFIER
        }

        ifIndex OBJECT-TYPE
                SYNTAX INTEGER
                ACCESS read-only
                STATUS mandatory
                DESCRIPTION
                        ""
                ::= { ifEntry 1 }

        ifDescr OBJECT-TYPE
                SYNTAX DisplayString
                ACCESS read-only
                STATUS mandatory
                DESCRIPTION
                        ""
                ::= { ifEntry 2 }

        ifType OBJECT-TYPE
                SYNTAX INTEGER
                ACCESS read-only
                STATUS mandatory
                DESCRIPTION
                        ""
                ::= { ifEntry 3 }

        ifMtu OBJECT-TYPE
                SYNTAX INTEGER
                ACCESS read-only
                STATUS mandatory
                DESCRIPTION
                        ""
                ::= { ifEntry 4 }

        ifSpeed OBJECT-TYPE
                SYNTAX Gauge
                ACCESS read-only
                STATUS mandatory
                DESCRIPTION
                        ""
                ::= { ifEntry 5 }

        ifPhysAddress OBJECT-TYPE
                SYNTAX PhysAddress
                ACCESS read-only
                STATUS mandatory
                DESCRIPTION
                        ""
                ::= { ifEntry 6 }

        ifAdminStatus OBJECT-TYPE
                SYNTAX INTEGER
                ACCESS read-write
                STATUS mandatory
                DESCRIPTION
                        ""
                ::= { ifEntry 7 }

        ifOperStatus OBJECT-TYPE
                SYNTAX INTEGER
                ACCESS read-only
                STATUS mandatory
                DESCRIPTION
                        ""
                ::= { ifEntry 8 }

        ifLastChange OBJECT-TYPE
                SYNTAX TimeTicks
                ACCESS read-only
                STATUS mandatory
                DESCRIPTION
                        ""
                ::= { ifEntry 9 }

        ifInOctets OBJECT-TYPE
                SYNTAX Counter
                ACCESS read-only
                STATUS mandatory
                DESCRIPTION
                        ""
                ::= { ifEntry 10 }

        ifInUcastPkts OBJECT-TYPE
                SYNTAX Counter
                ACCESS read-only
                STATUS mandatory
                DESCRIPTION
                        ""
                ::= { ifEntry 11 }

        ifInNUcastPkts OBJECT-TYPE
                SYNTAX Counter
                ACCESS read-only
                STATUS mandatory
                DESCRIPTION
                        ""
                ::= { ifEntry 12 }

        ifInDiscards OBJECT-TYPE
                SYNTAX Counter
                ACCESS read-only
                STATUS mandatory
                DESCRIPTION
                        ""
                ::= { ifEntry 13 }

        ifInErrors OBJECT-TYPE
                SYNTAX Counter
                ACCESS read-only
                STATUS mandatory
                DESCRIPTION
                        ""
                ::= { ifEntry 14 }

        ifInUnknownProtos OBJECT-TYPE
                SYNTAX Counter
                ACCESS read-only
                STATUS mandatory
                DESCRIPTION
                        ""
                ::= { ifEntry 15 }

        ifOutOctets OBJECT-TYPE
                SYNTAX Counter
                ACCESS read-only
                STATUS mandatory
                DESCRIPTION
                        ""
                ::= { ifEntry 16 }

        ifOutUcastPkts OBJECT-TYPE
                SYNTAX Counter
                ACCESS read-only
                STATUS mandatory
                DESCRIPTION
                        ""
                ::= { ifEntry 17 }

        ifOutNUcastPkts OBJECT-TYPE
                SYNTAX Counter
                ACCESS read-only
                STATUS mandatory
                DESCRIPTION
                        ""
                ::= { ifEntry 18 }

        ifOutDiscards OBJECT-TYPE
                SYNTAX Counter
                ACCESS read-only
                STATUS mandatory
                DESCRIPTION
                        ""
                ::= { ifEntry 19 }

        ifOutErrors OBJECT-TYPE
                SYNTAX Counter
                ACCESS read-only
                STATUS mandatory
                DESCRIPTION
                        ""
                ::= { ifEntry 20 }

        ifOutQLen OBJECT-TYPE
                SYNTAX Gauge
                ACCESS read-only
                STATUS mandatory
                DESCRIPTION
                        ""
                ::= { ifEntry 21 }

        ifSpecific OBJECT-TYPE
                SYNTAX OBJECT IDENTIFIER
                ACCESS read-only
                STATUS mandatory
                DESCRIPTION
                        ""
                ::= { ifEntry 22 }

        ipForwarding OBJECT-TYPE
                SYNTAX INTEGER
                ACCESS read-write
                STATUS mandatory
                DESCRIPTION
                        ""
                ::= { ip 1 }

        ipDefaultTTL OBJECT-TYPE
                SYNTAX INTEGER
                ACCESS read-write
                STATUS mandatory
                DESCRIPTION
                        ""
                ::= { ip 2 }

        ipInReceives OBJECT-TYPE
                SYNTAX Counter
                ACCESS read-only
                STATUS mandatory
                DESCRIPTION
                        ""
                ::= { ip 3 }

        ipInHdrErrors OBJECT-TYPE
                SYNTAX Counter
                ACCESS read-only
                STATUS mandatory
                DESCRIPTION
                        ""
                ::= { ip 4 }

        ipInAddrErrors OBJECT-TYPE
                SYNTAX Counter
                ACCESS read-only
                STATUS mandatory
                DESCRIPTION
                        ""
                ::= { ip 5 }

        ipForwDatagrams OBJECT-TYPE
                SYNTAX Counter
                ACCESS read-only
                STATUS mandatory
                DESCRIPTION
                        ""
                ::= { ip 6 }

        ipInUnknownProtos OBJECT-TYPE
                SYNTAX Counter
                ACCESS read-only
                STATUS mandatory
                DESCRIPTION
                        ""
                ::= { ip 7 }

        ipInDiscards OBJECT-TYPE
                SYNTAX Counter
                ACCESS read-only
                STATUS mandatory
                DESCRIPTION
                        ""
                ::= { ip 8 }

        ipInDelivers OBJECT-TYPE
                SYNTAX Counter
                ACCESS read-only
                STATUS mandatory
                DESCRIPTION
                        ""
                ::= { ip 9 }

        ipOutRequests OBJECT-TYPE
                SYNTAX Counter
                ACCESS read-only
                STATUS mandatory
                DESCRIPTION
                        ""
                ::= { ip 10 }

        ipOutDiscards OBJECT-TYPE
                SYNTAX Counter
                ACCESS read-only
                STATUS mandatory
                DESCRIPTION
                        ""
                ::= { ip 11 }

        ipOutNoRoutes OBJECT-TYPE
                SYNTAX Counter
                ACCESS read-only
                STATUS mandatory
                DESCRIPTION
                        ""
                ::= { ip 12 }

        ipReasmTimeout OBJECT-TYPE
                SYNTAX INTEGER
                ACCESS read-only
                STATUS mandatory
                DESCRIPTION
                        ""
                ::= { ip 13 }

        ipReasmReqds OBJECT-TYPE
                SYNTAX Counter
                ACCESS read-only
                STATUS mandatory
                DESCRIPTION
                        ""
                ::= { ip 14 }

        ipReasmOKs OBJECT-TYPE
                SYNTAX Counter
                ACCESS read-only
                STATUS mandatory
                DESCRIPTION
                        ""
                ::= { ip 15 }

        ipReasmFails OBJECT-TYPE
                SYNTAX Counter
                ACCESS read-only
                STATUS mandatory
                DESCRIPTION
                        ""
                ::= { ip 16 }

        ipFragOKs OBJECT-TYPE
                SYNTAX Counter
                ACCESS read-only
                STATUS mandatory
                DESCRIPTION
                        ""
                ::= { ip 17 }

        ipFragFails OBJECT-TYPE
                SYNTAX Counter
                ACCESS read-only
                STATUS mandatory
                DESCRIPTION
                        ""
                ::= { ip 18 }

        ipFragCreates OBJECT-TYPE
                SYNTAX Counter
                ACCESS read-only
                STATUS mandatory
                DESCRIPTION
                        ""
                ::= { ip 19 }

        ipAddrTable OBJECT-TYPE
                SYNTAX SEQUENCE OF IpAddrEntry
                ACCESS not-accessible
                STATUS mandatory
                DESCRIPTION
                        ""
                ::= { ip 20 }

        ipAddrEntry OBJECT-TYPE
                SYNTAX IpAddrEntry
                ACCESS not-accessible
                STATUS mandatory
                DESCRIPTION
                        ""
                INDEX { ipAdEntAddr }
                ::= { ipAddrTable 1 }

        IpAddrEntry ::= SEQUENCE { 
            ipAdEntAddr IpAddress,
            ipAdEntIfIndex INTEGER,
            ipAdEntNetMask IpAddress,
            ipAdEntBcastAddr INTEGER,
            ipAdEntReasmMaxSize INTEGER
        }

        ipAdEntAddr OBJECT-TYPE
                SYNTAX IpAddress
                ACCESS read-only
                STATUS mandatory
                DESCRIPTION
                        ""
                ::= { ipAddrEntry 1 }

        ipAdEntIfIndex OBJECT-TYPE
                SYNTAX INTEGER
                ACCESS read-only
                STATUS mandatory
                DESCRIPTION
                        ""
                ::= { ipAddrEntry 2 }

        ipAdEntNetMask OBJECT-TYPE
                SYNTAX IpAddress
                ACCESS read-only
                STATUS mandatory
                DESCRIPTION
                        ""
                ::= { ipAddrEntry 3 }

        ipAdEntBcastAddr OBJECT-TYPE
                SYNTAX INTEGER
                ACCESS read-only
                STATUS mandatory
                DESCRIPTION
                        ""
                ::= { ipAddrEntry 4 }

        ipAdEntReasmMaxSize OBJECT-TYPE
                SYNTAX INTEGER
                ACCESS read-only
                STATUS mandatory
                DESCRIPTION
                        ""
                ::= { ipAddrEntry 5 }

        ipRouteTable OBJECT-TYPE
                SYNTAX SEQUENCE OF IpRouteEntry
                ACCESS not-accessible
                STATUS mandatory
                DESCRIPTION
                        ""
                ::= { ip 21 }

        ipRouteEntry OBJECT-TYPE
                SYNTAX IpRouteEntry
                ACCESS not-accessible
                STATUS mandatory
                DESCRIPTION
                        ""
                INDEX { ipRouteDest }
                ::= { ipRouteTable 1 }

        IpRouteEntry ::= SEQUENCE { 
            ipRouteDest IpAddress,
            ipRouteIfIndex INTEGER,
            ipRouteMetric1 INTEGER,
            ipRouteMetric2 INTEGER,
            ipRouteMetric3 INTEGER,
            ipRouteMetric4 INTEGER,
            ipRouteNextHop IpAddress,
            ipRouteType INTEGER,
            ipRouteProto INTEGER,
            ipRouteAge INTEGER,
            ipRouteMask IpAddress,
            ipRouteMetric5 INTEGER,
            ipRouteInfo OBJECT IDENTIFIER
        }

        ipRouteDest OBJECT-TYPE
                SYNTAX IpAddress
                ACCESS read-write
                STATUS mandatory
                DESCRIPTION
                        ""
                ::= { ipRouteEntry 1 }

        ipRouteIfIndex OBJECT-TYPE
                SYNTAX INTEGER
                ACCESS read-write
                STATUS mandatory
                DESCRIPTION
                        ""
                ::= { ipRouteEntry 2 }

        ipRouteMetric1 OBJECT-TYPE
                SYNTAX INTEGER
                ACCESS read-write
                STATUS mandatory
                DESCRIPTION
                        ""
                ::= { ipRouteEntry 3 }

        ipRouteMetric2 OBJECT-TYPE
                SYNTAX INTEGER
                ACCESS read-write
                STATUS mandatory
                DESCRIPTION
                        ""
                ::= { ipRouteEntry 4 }

        ipRouteMetric3 OBJECT-TYPE
                SYNTAX INTEGER
                ACCESS read-write
                STATUS mandatory
                DESCRIPTION
                        ""
                ::= { ipRouteEntry 5 }

        ipRouteMetric4 OBJECT-TYPE
                SYNTAX INTEGER
                ACCESS read-write
                STATUS mandatory
                DESCRIPTION
                        ""
                ::= { ipRouteEntry 6 }

        ipRouteNextHop OBJECT-TYPE
                SYNTAX IpAddress
                ACCESS read-write
                STATUS mandatory
                DESCRIPTION
                        ""
                ::= { ipRouteEntry 7 }

        ipRouteType OBJECT-TYPE
                SYNTAX INTEGER
                ACCESS read-write
                STATUS mandatory
                DESCRIPTION
                        ""
                ::= { ipRouteEntry 8 }

        ipRouteProto OBJECT-TYPE
                SYNTAX INTEGER
                ACCESS read-only
                STATUS mandatory
                DESCRIPTION
                        ""
                ::= { ipRouteEntry 9 }

        ipRouteAge OBJECT-TYPE
                SYNTAX INTEGER
                ACCESS read-write
                STATUS mandatory
                DESCRIPTION
                        ""
                ::= { ipRouteEntry 10 }

        ipRouteMask OBJECT-TYPE
                SYNTAX IpAddress
                ACCESS read-write
                STATUS mandatory
                DESCRIPTION
                        ""
                ::= { ipRouteEntry 11 }

        ipRouteMetric5 OBJECT-TYPE
                SYNTAX INTEGER
                ACCESS read-write
                STATUS mandatory
                DESCRIPTION
                        ""
                ::= { ipRouteEntry 12 }

        ipRouteInfo OBJECT-TYPE
                SYNTAX OBJECT IDENTIFIER
                ACCESS read-only
                STATUS mandatory
                DESCRIPTION
                        ""
                ::= { ipRouteEntry 13 }

        ipNetToMediaTable OBJECT-TYPE
                SYNTAX SEQUENCE OF IpNetToMediaEntry
                ACCESS not-accessible
                STATUS mandatory
                DESCRIPTION
                        ""
                ::= { ip 22 }

        ipNetToMediaEntry OBJECT-TYPE
                SYNTAX IpNetToMediaEntry
                ACCESS not-accessible
                STATUS mandatory
                DESCRIPTION
                        ""
                INDEX { ipNetToMediaIfIndex, ipNetToMediaNetAddress }
                ::= { ipNetToMediaTable 1 }

        IpNetToMediaEntry ::= SEQUENCE { 
            ipNetToMediaIfIndex INTEGER,
            ipNetToMediaPhysAddress PhysAddress,
            ipNetToMediaNetAddress IpAddress,
            ipNetToMediaType INTEGER
        }

        ipNetToMediaIfIndex OBJECT-TYPE
                SYNTAX INTEGER
                ACCESS read-write
                STATUS mandatory
                DESCRIPTION
                        ""
                ::= { ipNetToMediaEntry 1 }

        ipNetToMediaPhysAddress OBJECT-TYPE
                SYNTAX PhysAddress
                ACCESS read-write
                STATUS mandatory
                DESCRIPTION
                        ""
                ::= { ipNetToMediaEntry 2 }

        ipNetToMediaNetAddress OBJECT-TYPE
                SYNTAX IpAddress
                ACCESS read-write
                STATUS mandatory
                DESCRIPTION
                        ""
                ::= { ipNetToMediaEntry 3 }

        ipNetToMediaType OBJECT-TYPE
                SYNTAX INTEGER
                ACCESS read-write
                STATUS mandatory
                DESCRIPTION
                        ""
                ::= { ipNetToMediaEntry 4 }

        ipRoutingDiscards OBJECT-TYPE
                SYNTAX Counter
                ACCESS read-only
                STATUS mandatory
                DESCRIPTION
                        ""
                ::= { ip 23 }

        icmpInMsgs OBJECT-TYPE
                SYNTAX Counter
                ACCESS read-only
                STATUS mandatory
                DESCRIPTION
                        ""
                ::= { icmp 1 }

        icmpInErrors OBJECT-TYPE
                SYNTAX Counter
                ACCESS read-only
                STATUS mandatory
                DESCRIPTION
                        ""
                ::= { icmp 2 }

        icmpInDestUnreachs OBJECT-TYPE
                SYNTAX Counter
                ACCESS read-only
                STATUS mandatory
                DESCRIPTION
                        ""
                ::= { icmp 3 }

        icmpInTimeExcds OBJECT-TYPE
                SYNTAX Counter
                ACCESS read-only
                STATUS mandatory
                DESCRIPTION
                        ""
                ::= { icmp 4 }

        icmpInParmProbs OBJECT-TYPE
                SYNTAX Counter
                ACCESS read-only
                STATUS mandatory
                DESCRIPTION
                        ""
                ::= { icmp 5 }

        icmpInSrcQuenchs OBJECT-TYPE
                SYNTAX Counter
                ACCESS read-only
                STATUS mandatory
                DESCRIPTION
                        ""
                ::= { icmp 6 }

        icmpInRedirects OBJECT-TYPE
                SYNTAX Counter
                ACCESS read-only
                STATUS mandatory
                DESCRIPTION
                        ""
                ::= { icmp 7 }

        icmpInEchos OBJECT-TYPE
                SYNTAX Counter
                ACCESS read-only
                STATUS mandatory
                DESCRIPTION
                        ""
                ::= { icmp 8 }

        icmpInEchoReps OBJECT-TYPE
                SYNTAX Counter
                ACCESS read-only
                STATUS mandatory
                DESCRIPTION
                        ""
                ::= { icmp 9 }

        icmpInTimestamps OBJECT-TYPE
                SYNTAX Counter
                ACCESS read-only
                STATUS mandatory
                DESCRIPTION
                        ""
                ::= { icmp 10 }

        icmpInTimestampReps OBJECT-TYPE
                SYNTAX Counter
                ACCESS read-only
                STATUS mandatory
                DESCRIPTION
                        ""
                ::= { icmp 11 }

        icmpInAddrMasks OBJECT-TYPE
                SYNTAX Counter
                ACCESS read-only
                STATUS mandatory
                DESCRIPTION
                        ""
                ::= { icmp 12 }

        icmpInAddrMaskReps OBJECT-TYPE
                SYNTAX Counter
                ACCESS read-only
                STATUS mandatory
                DESCRIPTION
                        ""
                ::= { icmp 13 }

        icmpOutMsgs OBJECT-TYPE
                SYNTAX Counter
                ACCESS read-only
                STATUS mandatory
                DESCRIPTION
                        ""
                ::= { icmp 14 }

        icmpOutErrors OBJECT-TYPE
                SYNTAX Counter
                ACCESS read-only
                STATUS mandatory
                DESCRIPTION
                        ""
                ::= { icmp 15 }

        icmpOutDestUnreachs OBJECT-TYPE
                SYNTAX Counter
                ACCESS read-only
                STATUS mandatory
                DESCRIPTION
                        ""
                ::= { icmp 16 }

        icmpOutTimeExcds OBJECT-TYPE
                SYNTAX Counter
                ACCESS read-only
                STATUS mandatory
                DESCRIPTION
                        ""
                ::= { icmp 17 }

        icmpOutParmProbs OBJECT-TYPE
                SYNTAX Counter
                ACCESS read-only
                STATUS mandatory
                DESCRIPTION
                        ""
                ::= { icmp 18 }

        icmpOutSrcQuenchs OBJECT-TYPE
                SYNTAX Counter
                ACCESS read-only
                STATUS mandatory
                DESCRIPTION
                        ""
                ::= { icmp 19 }

        icmpOutRedirects OBJECT-TYPE
                SYNTAX Counter
                ACCESS read-only
                STATUS mandatory
                DESCRIPTION
                        ""
                ::= { icmp 20 }

        icmpOutEchos OBJECT-TYPE
                SYNTAX Counter
                ACCESS read-only
                STATUS mandatory
                DESCRIPTION
                        ""
                ::= { icmp 21 }

        icmpOutEchoReps OBJECT-TYPE
                SYNTAX Counter
                ACCESS read-only
                STATUS mandatory
                DESCRIPTION
                        ""
                ::= { icmp 22 }

        icmpOutTimestamps OBJECT-TYPE
                SYNTAX Counter
                ACCESS read-only
                STATUS mandatory
                DESCRIPTION
                        ""
                ::= { icmp 23 }

        icmpOutTimestampReps OBJECT-TYPE
                SYNTAX Counter
                ACCESS read-only
                STATUS mandatory
                DESCRIPTION
                        ""
                ::= { icmp 24 }

        icmpOutAddrMasks OBJECT-TYPE
                SYNTAX Counter
                ACCESS read-only
                STATUS mandatory
                DESCRIPTION
                        ""
                ::= { icmp 25 }

        icmpOutAddrMaskReps OBJECT-TYPE
                SYNTAX Counter
                ACCESS read-only
                STATUS mandatory
                DESCRIPTION
                        ""
                ::= { icmp 26 }

        tcpRtoAlgorithm OBJECT-TYPE
                SYNTAX INTEGER
                ACCESS read-only
                STATUS mandatory
                DESCRIPTION
                        ""
                ::= { tcp 1 }

        tcpRtoMin OBJECT-TYPE
                SYNTAX INTEGER
                ACCESS read-only
                STATUS mandatory
                DESCRIPTION
                        ""
                ::= { tcp 2 }

        tcpRtoMax OBJECT-TYPE
                SYNTAX INTEGER
                ACCESS read-only
                STATUS mandatory
                DESCRIPTION
                        ""
                ::= { tcp 3 }

        tcpMaxConn OBJECT-TYPE
                SYNTAX INTEGER
                ACCESS read-only
                STATUS mandatory
                DESCRIPTION
                        ""
                ::= { tcp 4 }

        tcpActiveOpens OBJECT-TYPE
                SYNTAX Counter
                ACCESS read-only
                STATUS mandatory
                DESCRIPTION
                        ""
                ::= { tcp 5 }

        tcpPassiveOpens OBJECT-TYPE
                SYNTAX Counter
                ACCESS read-only
                STATUS mandatory
                DESCRIPTION
                        ""
                ::= { tcp 6 }

        tcpAttemptFails OBJECT-TYPE
                SYNTAX Counter
                ACCESS read-only
                STATUS mandatory
                DESCRIPTION
                        ""
                ::= { tcp 7 }

        tcpEstabResets OBJECT-TYPE
                SYNTAX Counter
                ACCESS read-only
                STATUS mandatory
                DESCRIPTION
                        ""
                ::= { tcp 8 }

        tcpCurrEstab OBJECT-TYPE
                SYNTAX Gauge
                ACCESS read-only
                STATUS mandatory
                DESCRIPTION
                        ""
                ::= { tcp 9 }

        tcpInSegs OBJECT-TYPE
                SYNTAX Counter
                ACCESS read-only
                STATUS mandatory
                DESCRIPTION
                        ""
                ::= { tcp 10 }

        tcpOutSegs OBJECT-TYPE
                SYNTAX Counter
                ACCESS read-only
                STATUS mandatory
                DESCRIPTION
                        ""
                ::= { tcp 11 }

        tcpRetransSegs OBJECT-TYPE
                SYNTAX Counter
                ACCESS read-only
                STATUS mandatory
                DESCRIPTION
                        ""
                ::= { tcp 12 }

        tcpConnTable OBJECT-TYPE
                SYNTAX SEQUENCE OF TcpConnEntry
                ACCESS not-accessible
                STATUS mandatory
                DESCRIPTION
                        ""
                ::= { tcp 13 }

        tcpConnEntry OBJECT-TYPE
                SYNTAX TcpConnEntry
                ACCESS not-accessible
                STATUS mandatory
                DESCRIPTION
                        ""
                INDEX { tcpConnLocalAddress, tcpConnLocalPort, tcpConnRemAddress, tcpConnRemPort }
                ::= { tcpConnTable 1 }

        TcpConnEntry ::= SEQUENCE { 
            tcpConnState INTEGER,
            tcpConnLocalAddress IpAddress,
            tcpConnLocalPort INTEGER,
            tcpConnRemAddress IpAddress,
            tcpConnRemPort INTEGER
        }

        tcpConnState OBJECT-TYPE
                SYNTAX INTEGER
                ACCESS read-write
                STATUS mandatory
                DESCRIPTION
                        ""
                ::= { tcpConnEntry 1 }

        tcpConnLocalAddress OBJECT-TYPE
                SYNTAX IpAddress
                ACCESS read-only
                STATUS mandatory
                DESCRIPTION
                        ""
                ::= { tcpConnEntry 2 }

        tcpConnLocalPort OBJECT-TYPE
                SYNTAX INTEGER
                ACCESS read-only
                STATUS mandatory
                DESCRIPTION
                        ""
                ::= { tcpConnEntry 3 }

        tcpConnRemAddress OBJECT-TYPE
                SYNTAX IpAddress
                ACCESS read-only
                STATUS mandatory
                DESCRIPTION
                        ""
                ::= { tcpConnEntry 4 }

        tcpConnRemPort OBJECT-TYPE
                SYNTAX INTEGER
                ACCESS read-only
                STATUS mandatory
                DESCRIPTION
                        ""
                ::= { tcpConnEntry 5 }

        tcpInErrs OBJECT-TYPE
                SYNTAX Counter
                ACCESS read-only
                STATUS mandatory
                DESCRIPTION
                        ""
                ::= { tcp 14 }

        tcpOutRsts OBJECT-TYPE
                SYNTAX Counter
                ACCESS read-only
                STATUS mandatory
                DESCRIPTION
                        ""
                ::= { tcp 15 }

        udpInDatagrams OBJECT-TYPE
                SYNTAX Counter
                ACCESS read-only
                STATUS mandatory
                DESCRIPTION
                        ""
                ::= { udp 1 }

        udpNoPorts OBJECT-TYPE
                SYNTAX Counter
                ACCESS read-only
                STATUS mandatory
                DESCRIPTION
                        ""
                ::= { udp 2 }

        udpInErrors OBJECT-TYPE
                SYNTAX Counter
                ACCESS read-only
                STATUS mandatory
                DESCRIPTION
                        ""
                ::= { udp 3 }

        udpOutDatagrams OBJECT-TYPE
                SYNTAX Counter
                ACCESS read-only
                STATUS mandatory
                DESCRIPTION
                        ""
                ::= { udp 4 }

        udpTable OBJECT-TYPE
                SYNTAX SEQUENCE OF UdpEntry
                ACCESS not-accessible
                STATUS mandatory
                DESCRIPTION
                        ""
                ::= { udp 5 }

        udpEntry OBJECT-TYPE
                SYNTAX UdpEntry
                ACCESS not-accessible
                STATUS mandatory
                DESCRIPTION
                        ""
                INDEX { udpLocalAddress, udpLocalPort }
                ::= { udpTable 1 }

        UdpEntry ::= SEQUENCE { 
            udpLocalAddress IpAddress,
            udpLocalPort INTEGER
        }

        udpLocalAddress OBJECT-TYPE
                SYNTAX IpAddress
                ACCESS read-only
                STATUS mandatory
                DESCRIPTION
                        ""
                ::= { udpEntry 1 }

        udpLocalPort OBJECT-TYPE
                SYNTAX INTEGER
                ACCESS read-only
                STATUS mandatory
                DESCRIPTION
                        ""
                ::= { udpEntry 2 }

        snmpInPkts OBJECT-TYPE
                SYNTAX Counter
                ACCESS read-only
                STATUS mandatory
                DESCRIPTION
                        ""
                ::= { snmp 1 }

        snmpOutPkts OBJECT-TYPE
                SYNTAX Counter
                ACCESS read-only
                STATUS mandatory
                DESCRIPTION
                        ""
                ::= { snmp 2 }

        snmpInBadVersions OBJECT-TYPE
                SYNTAX Counter
                ACCESS read-only
                STATUS mandatory
                DESCRIPTION
                        ""
                ::= { snmp 3 }

        snmpInBadCommunityNames OBJECT-TYPE
                SYNTAX Counter
                ACCESS read-only
                STATUS mandatory
                DESCRIPTION
                        ""
                ::= { snmp 4 }

        snmpInBadCommunityUses OBJECT-TYPE
                SYNTAX Counter
                ACCESS read-only
                STATUS mandatory
                DESCRIPTION
                        ""
                ::= { snmp 5 }

        snmpInASNParseErrs OBJECT-TYPE
                SYNTAX Counter
                ACCESS read-only
                STATUS mandatory
                DESCRIPTION
                        ""
                ::= { snmp 6 }

        snmpInTooBigs OBJECT-TYPE
                SYNTAX Counter
                ACCESS read-only
                STATUS mandatory
                DESCRIPTION
                        ""
                ::= { snmp 8 }

        snmpInNoSuchNames OBJECT-TYPE
                SYNTAX Counter
                ACCESS read-only
                STATUS mandatory
                DESCRIPTION
                        ""
                ::= { snmp 9 }

        snmpInBadValues OBJECT-TYPE
                SYNTAX Counter
                ACCESS read-only
                STATUS mandatory
                DESCRIPTION
                        ""
                ::= { snmp 10 }

        snmpInReadOnlys OBJECT-TYPE
                SYNTAX Counter
                ACCESS read-only
                STATUS mandatory
                DESCRIPTION
                        ""
                ::= { snmp 11 }

        snmpInGenErrs OBJECT-TYPE
                SYNTAX Counter
                ACCESS read-only
                STATUS mandatory
                DESCRIPTION
                        ""
                ::= { snmp 12 }

        snmpInTotalReqVars OBJECT-TYPE
                SYNTAX Counter
                ACCESS read-only
                STATUS mandatory
                DESCRIPTION
                        ""
                ::= { snmp 13 }

        snmpInTotalSetVars OBJECT-TYPE
                SYNTAX Counter
                ACCESS read-only
                STATUS mandatory
                DESCRIPTION
                        ""
                ::= { snmp 14 }

        snmpInGetRequests OBJECT-TYPE
                SYNTAX Counter
                ACCESS read-only
                STATUS mandatory
                DESCRIPTION
                        ""
                ::= { snmp 15 }

        snmpInGetNexts OBJECT-TYPE
                SYNTAX Counter
                ACCESS read-only
                STATUS mandatory
                DESCRIPTION
                        ""
                ::= { snmp 16 }

        snmpInSetRequests OBJECT-TYPE
                SYNTAX Counter
                ACCESS read-only
                STATUS mandatory
                DESCRIPTION
                        ""
                ::= { snmp 17 }

        snmpInGetResponses OBJECT-TYPE
                SYNTAX Counter
                ACCESS read-only
                STATUS mandatory
                DESCRIPTION
                        ""
                ::= { snmp 18 }

        snmpInTraps OBJECT-TYPE
                SYNTAX Counter
                ACCESS read-only
                STATUS mandatory
                DESCRIPTION
                        ""
                ::= { snmp 19 }

        snmpOutTooBigs OBJECT-TYPE
                SYNTAX Counter
                ACCESS read-only
                STATUS mandatory
                DESCRIPTION
                        ""
                ::= { snmp 20 }

        snmpOutNoSuchNames OBJECT-TYPE
                SYNTAX Counter
                ACCESS read-only
                STATUS mandatory
                DESCRIPTION
                        ""
                ::= { snmp 21 }

        snmpOutBadValues OBJECT-TYPE
                SYNTAX Counter
                ACCESS read-only
                STATUS mandatory
                DESCRIPTION
                        ""
                ::= { snmp 22 }

        snmpOutGenErrs OBJECT-TYPE
                SYNTAX Counter
                ACCESS read-only
                STATUS mandatory
                DESCRIPTION
                        ""
                ::= { snmp 24 }

        snmpOutGetRequests OBJECT-TYPE
                SYNTAX Counter
                ACCESS read-only
                STATUS mandatory
                DESCRIPTION
                        ""
                ::= { snmp 25 }

        snmpOutGetNexts OBJECT-TYPE
                SYNTAX Counter
                ACCESS read-only
                STATUS mandatory
                DESCRIPTION
                        ""
                ::= { snmp 26 }

        snmpOutSetRequests OBJECT-TYPE
                SYNTAX Counter
                ACCESS read-only
                STATUS mandatory
                DESCRIPTION
                        ""
                ::= { snmp 27 }

        snmpOutGetResponses OBJECT-TYPE
                SYNTAX Counter
                ACCESS read-only
                STATUS mandatory
                DESCRIPTION
                        ""
                ::= { snmp 28 }

        snmpOutTraps OBJECT-TYPE
                SYNTAX Counter
                ACCESS read-only
                STATUS mandatory
                DESCRIPTION
                        ""
                ::= { snmp 29 }

        snmpEnableAuthenTraps OBJECT-TYPE
                SYNTAX INTEGER
                ACCESS read-write
                STATUS mandatory
                DESCRIPTION
                        ""
                ::= { snmp 30 }

    END
